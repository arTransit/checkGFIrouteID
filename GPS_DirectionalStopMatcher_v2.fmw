FME workspace GPS_DirectionalStopMatcher_v2.fmw

Parameters:
- SourceDataset_SHAPE_9 = C:\AndrewRoss\Basedata\Transit\Stops\BusStops.shp   # Source ESRI Shape File(s)
- SourceDataset_SHAPE_6 = C:\AndrewRoss\Basedata\Transportation\DRA\Roads.shp   # Source ESRI Shape File(s)
- DestDataset_SQLITE3 = C:\AndrewRoss\Work\AR_Whistler\Data\whistlerDataTmp.db   # Destination SQLite3 Database File
- DestDataset_SHAPE = C:\AndrewRoss\Work\AR_Whistler\checkGFIrouteID   # Destination ESRI Shape Directory

Readers:
- SHAPE_1: SHAPE from $(SourceDataset_SHAPE_9)
- SHAPE_2: SHAPE from $(SourceDataset_SHAPE_6)

Writers:
- SQLITE3_1: SQLITE3 to $(DestDataset_SQLITE3)
- SHAPE_3: SHAPE to $(DestDataset_SHAPE) in BCALB-83

GPS: SQLCreator [off]
    FORMAT = SQLITE3
    DATASET = C:\AndrewRoss\Work\AR_Whistler\Data\whistlerData02.db
    SQL_STATEMENT = select * from GFI_GPS_TELEMETRY
    EXPOSED_ATTRIBUTE_LIST = _ID,BEARING,GPSID,LATITUDE,LONGITUDE,POINTCALC,SOURCE,SPEED
    RESULT -> 2DPointReplacer [off]
2DPointReplacer [off]
    YVALATTR = @Value(LATITUDE)
    XVALATTR = @Value(LONGITUDE)
    POINT -> Reprojector_3 [off]
Reprojector_3 [off]
    DEST = EPSG:26910
    SOURCE = BCALB-83
    RASTER_CELL_SIZE = Preserve Cells
    INTERPOLATION_TYPE_NAME = Nearest Neighbor
    STROKE_ARCS = Yes
    REPROJECTED -> NeighborFinder [input 1] [off]
BusStops (reader SHAPE_1)
    attributes: STOPID number(7,0), STOPNAME char(75), STOPCLASS number(2,0), LATITUDE number(15,10), LONGITUDE number(15,10), STATUS char(14), BCTREGION char(35), REGDIST char(35), BCTSYSTEM char(35), EXCHANGE char(35), PARKNRIDE char(35), AREANAME char(35), ADDNUMBER number(6,0), ADDSTREET char(35), ADDCITY char(35), STOPOWNER char(35), STOPRESP char(1), SBOWNER char(35), SBRESP char(35), BSSIGNAGE number(2,0), STOPIDDIS number(2,0), SIGNPOST number(2,0), SCHEDHOLD number(2,0), RTID number(2,0), BENCH number(2,0), SHELTER number(2,0), MAPDISPLAY number(2,0), ADVERT number(2,0), GARBAGEBIN number(2,0), HEATING number(2,0),
      LIGHTING number(2,0), SHADE number(2,0), ACCESSIBLE number(2,0), SURFACE number(2,0), CSD number(2,0), CURBHEIGHT number(3,0), CPLA number(2,0), TGSI number(2,0), SIDEWALK number(2,0), COMMENTS char(254), MODDATE date
    -> AttributeFilter
AttributeFilter
    ATTR_NAME = STATUS
    ATTR_VALUES = <BLANK>,<UNFILTERED>,Exists
    Exists -> Reprojector_2
Reprojector_2
    DEST = EPSG:26910
    SOURCE = BCALB-83
    RASTER_CELL_SIZE = Preserve Cells
    INTERPOLATION_TYPE_NAME = Nearest Neighbor
    STROKE_ARCS = Yes
    REPROJECTED -> StopAngleCalculator_2 [input 1]
Roads (reader SHAPE_2)
    attributes: ID number(8,0), NAME_FULL char(70), NAME_ID number(8,0), FROM_LEFT number(8,0), TO_LEFT number(8,0), FROM_RIGHT number(8,0), TO_RIGHT number(8,0), SINGLE_ADD number(8,0), PARITY_LFT char(1), PARITY_RGT char(1), CITY_LEFT char(50), CITY_RIGHT char(50), RD_CLASS char(12), NAME_BASE char(50), NAME_PREF char(2), NAME_PRTYP char(12), NAME_STRUC char(12), NAME_SUFF char(2), NAV_DIR char(1), RD_DIVIDED char(4)
    -> Reprojector
Reprojector
    DEST = EPSG:26910
    SOURCE = BCALB-83
    RASTER_CELL_SIZE = Preserve Cells
    INTERPOLATION_TYPE_NAME = Nearest Neighbor
    STROKE_ARCS = Yes
    REPROJECTED -> StopAngleCalculator_2 [input 2]
StopAngleCalculator_2
    -> AttributeRemover_2
AttributeRemover_2
    REMOVE_ATTRS = STOPNAME,STOPCLASS,LATITUDE,LONGITUDE,STATUS,BCTREGION,REGDIST,BCTSYSTEM,EXCHANGE,PARKNRIDE,AREANAME,ADDNUMBER,ADDSTREET,ADDCITY,STOPOWNER,STOPRESP,SBOWNER,SBRESP,BSSIGNAGE,STOPIDDIS,SIGNPOST,SCHEDHOLD,RTID,BENCH,SHELTER,MAPDISPLAY,ADVERT,GARBAGEBIN,HEATING,LIGHTING,SHADE,ACCESSIBLE,SURFACE,CSD,CURBHEIGHT,CPLA,TGSI,SIDEWALK,COMMENTS,MODDATE,ID,NAME_FULL,NAME_ID,FROM_LEFT,TO_LEFT,FROM_RIGHT,TO_RIGHT,SINGLE_ADD,PARITY_LFT,PARITY_RGT,CITY_LEFT,CITY_RIGHT,RD_CLASS,NAME_BASE,NAME_PREF,NAME_PRTYP,NAME_STRUC,NAME_SUFF,NAV_DIR,RD_DIVIDED,_overlaps,_distance,_angle,_candidate_angle,_candidate_label_angle,_closest_candidate_x,_closest_candidate_y,_closest_base_x,_closest_base_y
    -> NeighborFinder [input 2] [off]
    -> PythonCaller_2
NeighborFinder [off]
    MAX = 100
    CLOSE_LIST_NAME = close
    CANDIDATES_FIRST = No
    INSERT_VERTEX = No
    UNMATCHED_BASE -> AttributeCreator_4 [off]
    MATCHED -> PythonCaller [off]
PythonCaller [off]
    NEW_ATTRIBUTES = MATCH MATCHDISTANCE DIVERGENCE
    PYTHONSYMBOL = matchBusStops.FMEmatchBusStops
    -> Tester [off]
Tester [off]
    TEST_DESCRIPTION = ""
    TEST_CLAUSE = TEST "@Value(DIVERGENCE)" < "90"
    BOOL_OP = OR
    TEST_MODE = Automatic
    FAILED -> AttributeCreator_3 [off]
    PASSED -> AttributeCreator_2 [off]
AttributeCreator_2 [off]
    ATTR_LIST = STOPMATCHED,OK
    -> GFIGPS_STOPS_MATCH (writer SQLITE3_1) [off]
AttributeCreator_3 [off]
    ATTR_LIST = STOPMATCHED,NOMATCH
    -> GFIGPS_STOPS_MATCH (writer SQLITE3_1) [off]
AttributeCreator_4 [off]
    ATTR_LIST = STOPMATCHED,NONEIGHBOUR
    -> GFIGPS_STOPS_MATCH (writer SQLITE3_1) [off]
GFIGPS_STOPS_MATCH (writer SQLITE3_1) [off]
    attributes: _ID integer, BEARING float, LATITUDE float, LONGITUDE float, STANGLE float, DIVERGENCE float, STOPID integer, MATCH integer, SOURCE text, GPSID integer, STOPMATCHED text
Creator
    GEOMTYPE = Geometry Object
    NUM = 1
    CREATED -> AttributeCreator
AttributeCreator
    ATTR_LIST = CONFIGDATA,1,DISTANCE,50
    -> PythonCaller_2
PythonCaller_2
    PYTHONSYMBOL = CalculatePoint.FMEcalculatePoint
    -> PointConnector
PointConnector
    BREAKATTR = STOPID
    LINE -> PythonCaller_2_OUTPUT
    LINE -> Reprojector_4
PythonCaller_2_OUTPUT: Inspector
Reprojector_4
    DEST = BCALB-83
    SOURCE = EPSG:26910
    RASTER_CELL_SIZE = Preserve Cells
    INTERPOLATION_TYPE_NAME = Nearest Neighbor
    STROKE_ARCS = Yes
    REPROJECTED -> stopDirections (writer SHAPE_3)
stopDirections (writer SHAPE_3)
    attributes: STOPID number(20,0), STANGLE number(20,10), DISTANCE number(20,10)

FME custom transformer APCTelemetry

INPUT (input)
    -> AttributeExposer
AttributeExposer
    ATTR_LIST = LATITUDE,LONGITUDE
    -> Tester
Tester
    TEST_DESCRIPTION = ""
    TEST_CLAUSE:
      STRING_TEST "@Value(LATITUDE)" != "N/A"
      STRING_TEST "@Value(LONGITUDE)" != "N/A"
    BOOL_OP = AND
    TEST_LIST = &LATITUDE,!=,N/A,&LONGITUDE,!=,N/A
    TEST_MODE = String
    PASSED -> StringSearcher
    FAILED -> NO_LOCATION (output)
StringSearcher
    ATTRIBUTE = LATITUDE
    REGEXP = ,
    CASE = no
    NOT_MATCHED -> StringSearcher_2
    MATCHED -> NO_LOCATION (output)
StringSearcher_2
    ATTRIBUTE = LONGITUDE
    REGEXP = ,
    CASE = no
    NOT_MATCHED -> 2DPointReplacer
    MATCHED -> NO_LOCATION (output)
2DPointReplacer
    YVALATTR = @Value(LATITUDE)
    XVALATTR = @Value(LONGITUDE)
    POINT -> Reprojector
Reprojector
    DEST = UTM83-10
    SOURCE = WORLD-LL
    RASTER_CELL_SIZE = Preserve Cells
    INTERPOLATION_TYPE_NAME = Nearest Neighbor
    STROKE_ARCS = Yes
    REPROJECTED -> CoordinateExtractor
CoordinateExtractor
    Z_DEFAULT = 0
    IND = 0
    Y_ATTR = NORTHING
    X_ATTR = EASTING
    -> PythonCaller_2
PythonCaller_2
    PYTHONSYMBOL = APCTelemetry
    PYTHONSOURCE:
      import math

      class APCTelemetry(object):

          def __init__(self):
              # Variables to pass attribute values from one feature to the next.
              self.pX = 0
              self.pY = 0
              self.pBus = 0
              self.pEpoch = 0
              self.pSpeed = 0

              self.pBearing = 0
              self.pTrend = 0

          def input(self,feature):
              # Variables to store current attribute values.
              self.bus = feature.getAttribute("BUS")
              self.x = feature.getAttribute("EASTING")
              self.y = feature.getAttribute("NORTHING")
              self.epoch = float(feature.getAttribute("EDT"))

              # If this is the first record for this bus the bus has not moved
              if self.bus != self.pBus:
                  feature.setAttribute("DISTANCE",0)
                  feature.setAttribute("BEARING",0)
                  feature.setAttribute("SPEED",0)
                  feature.setAttribute("ELAPSED",0)
                  self.speed = 0
                  self.bearingDeg = 0
              #If this is the not the first record for this bus we can calculate it's movement
              else:
                  # Calculate the elapsed time between records in seconds
                  self.elapsed = self.epoch-self.pEpoch
                  feature.setAttribute("ELAPSED",self.elapsed)

                  if self.elapsed > 0:
                      # Delta X / Delta Y
                      self.dX = math.sqrt(math.pow(float(self.x)-float(self.pX),2))
                      self.dY = math.sqrt(math.pow(float(self.y)-float(self.pY),2))

                      # Calculate distance pythagoreas
                      self.distance = float(math.sqrt(math.pow(self.dX,2)+math.pow(self.dY,2)))
                      feature.setAttribute("DISTANCE",self.distance)

                      if self.distance > 20:

                          # Calculate bearing using trigonometry.
                          self.bearingRad = math.atan2(self.dY,self.dX)
                          self.bearingDeg = math.degrees(self.bearingRad)

                          # Determine quadrant and add corresponding number of degrees
                          if float(self.x)-float(self.pX) > 0 and float(self.y)-float(self.pY) >0:
                              self.bearingDeg = 90 - self.bearingDeg
                          elif float(self.x)-float(self.pX) > 0 and float(self.y)-float(self.pY) <0:
                              self.bearingDeg = self.bearingDeg + 90
                          elif float(self.x)-float(self.pX) < 0 and float(self.y)-float(self.pY) <0:
                              self.bearingDeg = 270 - self.bearingDeg
                          elif float(self.x)-float(self.pX) < 0 and float(self.y)-float(self.pY) >0:
                              self.bearingDeg = 270 + self.bearingDeg
                          feature.setAttribute("BEARING",self.bearingDeg)

                          #Calculate speed
                          self.speed = self.distance/self.elapsed*3.6
                          feature.setAttribute("SPEED",self.speed)

                          self.dTrend = (self.bearingDeg + self.pBearing)/2
                          feature.setAttribute("DTREND",self.dTrend)
                          self.pBearing = self.bearingDeg
                          self.pTrend = self.dTrend
                      else:
                          feature.setAttribute("BEARING",self.pBearing)
                          feature.setAttribute("DTREND",self.pTrend)
                          feature.setAttribute("SPEED",self.pSpeed)
                  # if there is no elapsed time between records SPEED and BEARING are equal to the previous record
                  else:
                      feature.setAttribute("DISTANCE",0)
                      feature.setAttribute("BEARING",self.pBearing)
                      feature.setAttribute("SPEED",self.pSpeed)
                      feature.setAttribute("ELAPSED",0)
                      feature.setAttribute("DTREND",self.pTrend)

              #Pass variables to the next feature
              self.pX = self.x
              self.pY = self.y
              self.pEpoch = self.epoch
              self.pBus = self.bus
              self.pSpeed = self.speed

              self.pyoutput(feature)

          def close(self):
               pass
    -> OUTPUT (output)
OUTPUT (output)
NO_LOCATION (output)

FME custom transformer StopAngleCalculator

Stops (input)
    -> AttributeExposer
AttributeExposer
    ATTR_LIST = STOPID,STOPNAME
    -> PointOnLineOverlayer [input 1]
    -> AnchoredSnapper [input 2]
    -> NeighborFinder [input 1]
DRA (input)
    -> PointOnLineOverlayer [input 2]
PointOnLineOverlayer
    TOLERANCE = 50
    OV_ATTR = _overlaps
    LINE -> AnchoredSnapper [input 1]
AnchoredSnapper
    TOLERANCE = 50
    EXTEND_LINES = NEVER
    SNAPTYPE_PARAM = End Point Snapping
    SNAPPED -> NeighborFinder [input 2]
NeighborFinder
    GROUP_BY = STOPID
    MAX = 50
    CANDIDATES_FIRST = No
    INSERT_VERTEX = No
    MATCHED -> PythonCaller
PythonCaller
    PYTHONSYMBOL = MyPythonFactory
    PYTHONSOURCE:
      import math

      class MyPythonFactory(object):
        def input(self,feature):
            self.pX = feature.getAttribute("_closest_base_x")
            self.pY = feature.getAttribute("_closest_base_y")
            self.x = feature.getAttribute("_closest_candidate_x")
            self.y = feature.getAttribute("_closest_candidate_y")
            # Delta X / Delta Y
            self.dX = math.sqrt(math.pow(float(self.x)-float(self.pX),2))
            self.dY = math.sqrt(math.pow(float(self.y)-float(self.pY),2))
            # Calculate bearing using trigonometry.
            self.angleRad = math.atan2(self.dY,self.dX)
            self.angleDeg = math.degrees(self.angleRad)
            # Determine quadrant and add corresponding number of degrees
            if float(self.x)-float(self.pX) > 0 and float(self.y)-float(self.pY) >0:
                self.angleDeg = 90 - self.angleDeg
            elif float(self.x)-float(self.pX) > 0 and float(self.y)-float(self.pY) <0:
                self.angleDeg = self.angleDeg + 90
            elif float(self.x)-float(self.pX) < 0 and float(self.y)-float(self.pY) <0:
                self.angleDeg = 270 - self.angleDeg
            elif float(self.x)-float(self.pX) < 0 and float(self.y)-float(self.pY) >0:
                self.angleDeg = 270 + self.angleDeg
            feature.setAttribute("STANGLE",self.angleDeg)

            self.pyoutput(feature)
    -> Output (output)
Output (output)

FME workspace GFI_fillinNonMatched.fmw

Parameters:
- DestDataset_SQLITE3 = C:\AndrewRoss\Work\AR_Whistler\Data\whistlerDataTmp.db   # Destination SQLite3 Database File

Writers:
- SQLITE3_1: SQLITE3 to $(DestDataset_SQLITE3)

GFImatchedForward: SQLCreator
    FORMAT = SQLITE3
    DATASET = C:\AndrewRoss\Work\AR_Whistler\Data\whistlerData02.db
    SQL_STATEMENT:
      select GFI._ID, GFI.BUS,GFI.TIMESTAMP,
      GFISTOPS_MATCH_TMP.MATCH, GFISTOPS_MATCH_TMP.SOURCE, GFISTOPS_MATCH_TMP.GPSID, GFISTOPS_MATCH_TMP.STOPMATCHED
      from GFI,GFISTOPS_MATCH_TMP
      where GFI._ID=GFISTOPS_MATCH_TMP._ID
      order by GFI.BUS,GFI.TIMESTAMP
    EXPOSED_ATTRIBUTE_LIST = _ID,BUS,GPSID,SOURCE,STOPMATCHED,TIMESTAMP,MATCH
    RESULT -> PythonCaller
PythonCaller
    NEW_ATTRIBUTES = TIMEDIFF
    PYTHONSYMBOL = Fillin.FMEFillInStops
    -> Tester
Tester
    TEST_DESCRIPTION = ""
    TEST_CLAUSE = TEST "@Value(STOPMATCHED)" = "OK"
    BOOL_OP = OR
    TEST_MODE = Automatic
    PASSED -> GFI_MATCHFILLED (writer SQLITE3_1)
    FAILED -> Tester_2
Tester_2
    TEST_DESCRIPTION = ""
    TEST_CLAUSE:
      TEST "@Value(TIMEDIFF)" < "300"
      TEST "@Value(MATCH)" > "0"
    BOOL_OP = AND
    TEST_MODE = Automatic
    PASSED -> GFI_MATCHFILLED (writer SQLITE3_1)
    FAILED -> Sorter
Sorter
    SORT_PARM = BUS NUMERIC ASCENDING TIMESTAMP NUMERIC DESCENDING
    SORTED -> PythonCaller_2
PythonCaller_2
    NEW_ATTRIBUTES = TIMEDIFF
    PYTHONSYMBOL = Fillin.FMEFillInStops
    -> GFI_MATCHFILLED (writer SQLITE3_1)
GFI_MATCHFILLED (writer SQLITE3_1)
    attributes: _ID integer, BUS integer, TIMESTAMP integer, MATCH integer, SOURCE text, GPSID integer, STOPMATCHED text, TIMEDIFF integer

FME workspace _test.fmw

Parameters:
- DestDataset_SHAPE = C:\AndrewRoss\Work\AR_Whistler\checkGFIrouteID   # Destination ESRI Shape Directory
- DestDataset_SHAPE_3 = C:\AndrewRoss\Work\AR_Whistler\checkGFIrouteID   # Destination ESRI Shape Directory

Writers:
- SHAPE_1: SHAPE to $(DestDataset_SHAPE)
- SHAPE_2: SHAPE to $(DestDataset_SHAPE_3)

Creator [off]
    GEOMTYPE = Geometry Object
    GEOM = <?xml version="1.0" encoding="US_ASCII" standalone="no" ?><geometry><point><coord x="1" y="1"/></point></geometry>
    NUM = 1
    COORDSYS = LL
    CREATED -> AttributeCreator
Creator_2 [off]
    GEOMTYPE = Geometry Object
    GEOM = <?xml version="1.0" encoding="US_ASCII" standalone="no" ?><geometry><point><coord x="2" y="2"/></point></geometry>
    NUM = 1
    CREATED -> AttributeCreator
AttributeCreator [off]
    ATTR_LIST = CLASS,1
    -> Aggregator
    -> PointConnector
Aggregator [off]
    ACCUM_ATTRS_NAME = No
    GROUP_BY = CLASS
    SEP = ,
    ORDERED = No
    CONTAIN_INDIVID_GEOMS = No
    AGGREGATE -> PointConnector
PointConnector [off]
    BREAKATTR = CLASS
    POINT -> PointConnector_POINT
    LINE -> PointConnector_LINE
    POLYGON -> PointConnector_POLYGON
PointConnector_POINT: Inspector [off]
PointConnector_LINE: Inspector [off]
PointConnector_POLYGON: Inspector
SQLCreator
    FORMAT = SQLITE3
    DATASET = C:\AndrewRoss\Work\AR_Whistler\Data\whistlerData02.db
    SQL_STATEMENT:
      select GEO.*,GFI.ROUTE as CODE,ROUTE_PATTERNS.route as ROUTEID from (
      select * from GFI_GPS_TELEMETRY
      union
      select * from GFI_APC_TELEMETRY
      ) GEO join GFI on GEO._ID=GFI._ID left join ROUTE_PATTERNS on ROUTE_PATTERNS.code=GFI.ROUTE
    COORDSYS = BCALB-83
    EXPOSED_ATTRIBUTE_LIST = _ID,BEARING,CODE,GPSID,LATITUDE,LONGITUDE,POINTCALC,ROUTEID,SOURCE,SPEED
    RESULT -> 2DPointReplacer_2
2DPointReplacer_2
    YVALATTR = @Value(LATITUDE)
    XVALATTR = @Value(LONGITUDE)
    POINT -> Sorter
    POINT -> gfi_mismatched (writer SHAPE_2)
gfi_mismatched (writer SHAPE_2)
    attributes: _ID char(20), LONGITUDE char(20), ROUTEID char(20), CODE char(20), SPEED char(20), BEARING char(20), SOURCE char(20), GPSID char(20), POINTCALC char(20), LATITUDE char(20)
SQLCreator_2
    FORMAT = SQLITE3
    DATASET = C:\AndrewRoss\Work\AR_Whistler\Data\whistlerData02.db
    SQL_STATEMENT:
      select V_GFISTOPDATA._ID, V_GFISTOPDATA.route as ROUTEID, V_GFISTOPDATA.STOPID,ROUTESTOPLIST.STOPID as GOODSTOP,
      BUSSTOPS.LONGITUDE, BUSSTOPS.LATITUDE
      from V_GFISTOPDATA
      join BUSSTOPS on BUSSTOPS.STOPID=V_GFISTOPDATA.STOPID
      left join ROUTESTOPLIST on ROUTESTOPLIST.ROUTEID=V_GFISTOPDATA.route and ROUTESTOPLIST.STOPID=V_GFISTOPDATA.STOPID
      where V_GFISTOPDATA.route >0
    EXPOSED_ATTRIBUTE_LIST = BUSSTOPS.LATITUDE,BUSSTOPS.LONGITUDE,GOODSTOP,ROUTEID,V_GFISTOPDATA._ID,V_GFISTOPDATA.STOPID
    RESULT -> AttributeRenamer
AttributeRenamer
    ATTR_LIST = BUSSTOPS.LATITUDE,LAT,"",BUSSTOPS.LONGITUDE,LON,"",V_GFISTOPDATA._ID,_ID,"",V_GFISTOPDATA.STOPID,STOPID,""
    -> Tester
Tester
    TEST_DESCRIPTION = ""
    TEST_CLAUSE = TEST "GOODSTOP" ATTRIBUTE_IS_NULL "<Unused>"
    BOOL_OP = AND
    TEST_MODE = Automatic
    PASSED -> 2DPointReplacer
2DPointReplacer
    YVALATTR = @Value(LAT)
    XVALATTR = @Value(LON)
    POINT -> Reprojector
Reprojector
    DEST = BCALB-83
    SOURCE = LL
    RASTER_CELL_SIZE = Preserve Cells
    INTERPOLATION_TYPE_NAME = Nearest Neighbor
    STROKE_ARCS = Yes
    REPROJECTED -> Sorter
Sorter
    SORT_PARM = _ID NUMERIC ASCENDING
    SORTED -> PointConnector_2
PointConnector_2
    LIST_NAME = ATT
    BREAKATTR = _ID
    LINE -> GFIlines (writer SHAPE_1)
GFIlines (writer SHAPE_1)
    attributes: LAT char(20), CODE char(20), LONGITUDE char(20), SOURCE char(20), ROUTEID char(20), _ID char(20), STOPID char(20), LATITUDE char(20), LON char(20), BEARING char(20), SPEED char(20), GPSID char(20), POINTCALC char(20), GOODSTOP char(20)

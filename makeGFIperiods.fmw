FME workspace makeGFIperiods.fmw

Parameters:
- DestDataset_SQLITE3 = C:\AndrewRoss\Work\AR_Whistler\Data\whistlerData02.db   # Destination SQLite3 Database File
- SourceDataset_SHAPE = C:\AndrewRoss\Work\AR_Whistler\Input\Routes.shp   # Source ESRI Shape File(s)

Readers:
- SHAPE_1: SHAPE from $(SourceDataset_SHAPE)

Writers:
- SQLITE3_1: SQLITE3 to $(DestDataset_SQLITE3)

SQLCreator [off]
    FORMAT = SQLITE3
    DATASET = C:\AndrewRoss\Work\AR_Whistler\Data\whistlerData02.db
    SQL_STATEMENT = "select * from GFI "
    EXPOSED_ATTRIBUTE_LIST = _ID,BUS,BUSDAY,DAY,DAYOFWEEK,DAYTYPE,HOUR,ID,LOC_N,MINUTE,MONTH,N,ROUTE,SECOND,SEQTR,TIMESTAMP,TS,TYPE,YEAR
    RESULT -> Sorter
Sorter [off]
    SORT_PARM = BUS NUMERIC ASCENDING ROUTE NUMERIC ASCENDING TIMESTAMP NUMERIC ASCENDING
    SORTED -> PythonCaller
PythonCaller [off]
    NEW_ATTRIBUTES = BUSID ROUTEID FROMTIME TOTIME
    PYTHONSYMBOL = calculatePeriods.FMEgfiPeriods
    -> GFIRUNPERIODS (writer SQLITE3_1)
GFIRUNPERIODS (writer SQLITE3_1) [off]
    attributes: BUSID integer, ROUTEID integer, FROMTIME integer, TOTIME integer
SQLCreator_2
    FORMAT = SQLITE3
    DATASET = C:\AndrewRoss\Work\AR_Whistler\Data\whistlerData02.db
    SQL_STATEMENT = select * from v_gfipoints
    EXPOSED_ATTRIBUTE_LIST = _ID,BEARING,GPSID,LATITUDE,LONGITUDE,POINTCALC,ROUTE,ROUTEID,SOURCE,SPEED
    RESULT -> 2DPointReplacer
2DPointReplacer
    YVALATTR = @Value(LATITUDE)
    XVALATTR = @Value(LONGITUDE)
    POINT -> NeighborFinder [input 1]
Routes (reader SHAPE_1)
    attributes: ROUTEID char(5), PATTERNID char(20), PATTERNID2 number(4,0), DIRECTION char(20), GROUP char(8), HIERARCHY number(1,0), WCHEND number(2,0), LENGTH number(8,1), PTRNCNT number(5,0), DISTANCE number(8,1), SEGSEQ number(3,0), GLOBALRANK number(4,0), INDIVLINE number(1,0), ENDOFPATH number(1,0), ID number(8,0), NAV_DIR char(3), SNIPFROM number(4,1), SNIPTO number(4,1)
    -> Aggregator
Aggregator
    ACCUM_ATTRS_NAME = No
    GROUP_BY = ROUTEID
    SEP = ,
    ORDERED = No
    CONTAIN_INDIVID_GEOMS = No
    AGGREGATE -> NeighborFinder [input 2]
NeighborFinder
    GROUP_BY = ROUTEID
    MAX = 200
    CANDIDATES_FIRST = No
    TREAT_POLYGON_AS = Lines
    INSERT_VERTEX = No
    MATCHED -> NeighborFinder_MATCHED
    UNMATCHED_BASE -> NeighborFinder_UNMATCHED_BASE
NeighborFinder_MATCHED: Inspector
NeighborFinder_UNMATCHED_BASE: Inspector
